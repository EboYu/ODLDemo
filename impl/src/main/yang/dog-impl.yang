module dog-impl {
    yang-version 1;
    namespace "urn:opendaylight:params:xml:ns:yang:dog:impl";
    prefix "dog-impl";

    import config { prefix config; revision-date 2013-04-05; }
    import opendaylight-md-sal-binding { prefix md-sal-binding; revision-date 2013-10-28;}

    description
        "Service definition";

    revision "2017-03-23" {
        description
            "Initial revision";
    }

    identity dog {
        base config:module-type;
        config:java-name-prefix dog;
    }

    augment "/config:modules/config:module/config:configuration" {
        case dog {
            when "/config:modules/config:module/config:type = 'dog'";
            container data-broker {
                uses config:service-ref {
                    refine type {
                        mandatory true;
                        config:required-identity md-sal-binding:binding-async-data-broker;
                    }
                }
            }
            container rpc-registry {
                 uses config:service-ref {
                     refine type {
                        mandatory true;
                        config:required-identity md-sal-binding:binding-rpc-registry;
                     }
                 }
            }
        }
    }

}
