module chicken-impl {
    yang-version 1;
    namespace "urn:opendaylight:params:xml:ns:yang:chicken:impl";
    prefix "chicken-impl";

    import config { prefix config; revision-date 2013-04-05; }
    import opendaylight-md-sal-binding { prefix md-sal-binding; revision-date 2013-10-28;}

    description
        "Service definition";

    revision "2017-03-23" {
        description
            "Initial revision";
    }

    identity chicken {
        base config:module-type;
        config:java-name-prefix chicken;
    }

    augment "/config:modules/config:module/config:configuration" {
        case chicken {
            when "/config:modules/config:module/config:type = 'chicken'";
            container data-broker {
                uses config:service-ref {
                    refine type {
                        mandatory true;
                        config:required-identity md-sal-binding:binding-async-data-broker;
                    }
                }
            }

            container rpc-registry {
                             uses config:service-ref {
                                refine type {
                                     mandatory true;
                                     config:required-identity md-sal-binding:binding-rpc-registry;
                                 }
                              }
            }

        }
    }
}
