module exampleapp {
    yang-version 1;
    namespace "urn:opendaylight:params:xml:ns:yang:exampleapp";
    prefix "exampleapp";

    revision "2017-03-23" {
        description "Initial revision of exampleapp model";
    }

    rpc service-account{
        input {
              leaf name {
                      type string;
              }
              leaf description {
                      type string;
              }
              leaf traceID {
                                  type string;
               }

              leaf num {
                  type uint32;
              }

        }

        output {
               leaf service_name {
                       type string;
               }                 
        }
    }
}
